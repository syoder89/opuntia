IMAGESTREAM-QOS-MIB DEFINITIONS ::= BEGIN

IMPORTS
    MODULE-IDENTITY, OBJECT-TYPE, Counter32, Gauge32,
    Integer32,
    NOTIFICATION-TYPE                        FROM SNMPv2-SMI
    TEXTUAL-CONVENTION, DisplayString        FROM SNMPv2-TC
    OBJECT-GROUP,
    NOTIFICATION-GROUP                       FROM SNMPv2-CONF
    router                                   FROM IMAGESTREAM-ROOT-MIB;


qosMIB MODULE-IDENTITY
    LAST-UPDATED "201009020000Z"
    ORGANIZATION "ImageStream Internet Solutions, Inc."
    CONTACT-INFO
            "   Scott Yoder
                ImageStream Internet Solutions, Inc.
                7900 E. 8th Rd.
                Plymouth, IN 46563
                US

                574-935-8484
                support@imagestream.com"
    DESCRIPTION
            "The MIB module to describe generic objects for ImageStream's
            class-based QoS system."

    REVISION      "201009020000Z"
    DESCRIPTION
            "Initial revision."
    ::= { router 2 }


qosConformance OBJECT IDENTIFIER ::= { qosMIB 2 }
qosGroups      OBJECT IDENTIFIER ::= { qosConformance 1 }

-- QoSServiceIndex contains the semantics of qosServicePolicyIndex and should be used
-- for any objects defined in other MIB modules that need these semantics.

QosServicePolicyIndex ::= TEXTUAL-CONVENTION
    DISPLAY-HINT "d"
    STATUS       current
    DESCRIPTION
            "A unique value, greater than zero, for each QoS Service
            in the managed system. The value for each QoSinterface sub-layer
            must remain constant at least from one re-initialization of the
            entity's network management system to the next re-initialization."
    SYNTAX       Integer32 (1..2147483647)

QosServicePolicyIndexOrZero ::= TEXTUAL-CONVENTION
    DISPLAY-HINT "d"
    STATUS       current
    DESCRIPTION
            "An index where 0 is allowed."
    SYNTAX       Integer32 (0..2147483647)

-- the qosServicePolicy table

qosServicePolicyTable OBJECT-TYPE
    SYNTAX      SEQUENCE OF QosServicePolicyEntry
    MAX-ACCESS  not-accessible
    STATUS      current
    DESCRIPTION
            "A list of QoSinterface entries.  The number of entries is
            given by the value of qosServicePolicyNumber."
    ::= { qosMIB 1 }

qosServicePolicyEntry OBJECT-TYPE
    SYNTAX      QosServicePolicyEntry
    MAX-ACCESS  not-accessible
    STATUS      current
    DESCRIPTION
            "An entry containing management information applicable to a
            particular QoSinterface."
    INDEX   { qosServicePolicyIndex }
    ::= { qosServicePolicyTable 1 }

QosServicePolicyEntry ::=
    SEQUENCE {
	qosServicePolicyIndex	   QosServicePolicyIndex, 
        qosIfName                  DisplayString,
        qosIfIndex                 Integer32,
        qosPolicy                  DisplayString,
        qosService                 DisplayString,
        qosType                    DisplayString,
        qosPriority                Integer32,
        qosRxMin                   Integer32,
        qosRxMax                   Integer32,
        qosRxPackets               Counter32,
        qosRxBytes                 Counter32,
        qosRxDropped               Counter32,
        qosRxOverlimits            Counter32,
        qosRxBacklogPackets        Integer32,
        qosRxBacklogBytes          Integer32,
        qosRxBacklogMs             Integer32,
        qosTxMin                   Integer32,
        qosTxMax                   Integer32,
        qosTxPackets               Counter32,
        qosTxBytes                 Counter32,
        qosTxDropped               Counter32,
        qosTxOverlimits            Counter32,
        qosTxBacklogPackets        Integer32,
        qosTxBacklogBytes          Integer32,
        qosTxBacklogMs             Integer32
    }

qosServicePolicyIndex OBJECT-TYPE
    SYNTAX      QosServicePolicyIndex
    MAX-ACCESS  read-only
    STATUS      current
    DESCRIPTION
            "A unique value, greater than zero, for each QoS service."
    ::= { qosServicePolicyEntry 1 }

qosIfName OBJECT-TYPE
    SYNTAX      DisplayString (SIZE (0..255))
    MAX-ACCESS  read-only
    STATUS      current
    DESCRIPTION
            "A textual string containing information about the interface
            name the QoS service is applied."
    ::= { qosServicePolicyEntry 2 }

qosIfIndex OBJECT-TYPE
    SYNTAX      Integer32
    MAX-ACCESS  read-only
    STATUS      current
    DESCRIPTION
            "The interface index that this QoS service is applied to."
    ::= { qosServicePolicyEntry 3 }

qosPolicy OBJECT-TYPE
    SYNTAX      DisplayString (SIZE (0..255))
    MAX-ACCESS  read-only
    STATUS      current
    DESCRIPTION
            "A textual string containing information about the policy
            name for this QoS service."
    ::= { qosServicePolicyEntry 4 }

qosService OBJECT-TYPE
    SYNTAX      DisplayString (SIZE (0..255))
    MAX-ACCESS  read-only
    STATUS      current
    DESCRIPTION
            "A textual string containing information about the service
            name for this QoS service."
    ::= { qosServicePolicyEntry 5 }

qosType OBJECT-TYPE
    SYNTAX      DisplayString (SIZE (0..255))
    MAX-ACCESS  read-only
    STATUS      current
    DESCRIPTION
            "A textual string containing information about the service
            type (LLQ/CBQ) for this QoS service."
    ::= { qosServicePolicyEntry 6 }

qosPriority OBJECT-TYPE
    SYNTAX      Integer32
    MAX-ACCESS  read-only
    STATUS      current
    DESCRIPTION
            "The priority value for for this QoS service."
    ::= { qosServicePolicyEntry 7 }

qosRxMin OBJECT-TYPE
    SYNTAX      Integer32
    MAX-ACCESS  read-only
    STATUS      current
    DESCRIPTION
            "The minimum receive rate in Kbps for this QoS service."
    ::= { qosServicePolicyEntry 8 }

qosRxMax OBJECT-TYPE
    SYNTAX      Integer32
    MAX-ACCESS  read-only
    STATUS      current
    DESCRIPTION
            "The maximum receive rate in Kbps for this QoS service."
    ::= { qosServicePolicyEntry 9 }

qosRxPackets OBJECT-TYPE
    SYNTAX      Counter32
    MAX-ACCESS  read-only
    STATUS      current
    DESCRIPTION
            "The number of packets received for this QoS service."
    ::= { qosServicePolicyEntry 10 }

qosRxBytes OBJECT-TYPE
    SYNTAX      Counter32
    MAX-ACCESS  read-only
    STATUS      current
    DESCRIPTION
            "The number of bytes received for this QoS service."
    ::= { qosServicePolicyEntry 11 }

qosRxDropped OBJECT-TYPE
    SYNTAX      Counter32
    MAX-ACCESS  read-only
    STATUS      current
    DESCRIPTION
            "The number of packets dropped in the receive direction for this
            QoS service."
    ::= { qosServicePolicyEntry 12 }

qosRxOverlimits OBJECT-TYPE
    SYNTAX      Counter32
    MAX-ACCESS  read-only
    STATUS      current
    DESCRIPTION
            "The number of packets rate-shaped but not dropped in the receive
            direction for this QoS service."
    ::= { qosServicePolicyEntry 13 }

qosRxBacklogPackets OBJECT-TYPE
    SYNTAX      Integer32
    MAX-ACCESS  read-only
    STATUS      current
    DESCRIPTION
            "The number of packets currently queued in the receive direction 
            for this QoS service."
    ::= { qosServicePolicyEntry 14 }

qosRxBacklogBytes OBJECT-TYPE
    SYNTAX      Integer32
    MAX-ACCESS  read-only
    STATUS      current
    DESCRIPTION
            "The number of bytes currently queued in the receive direction 
            for this QoS service."
    ::= { qosServicePolicyEntry 15 }

qosRxBacklogMs OBJECT-TYPE
    SYNTAX      Integer32
    MAX-ACCESS  read-only
    STATUS      current
    DESCRIPTION
            "The amount of time in milliseconds required to receive the
            queued data at the class' maximum rate in the receive direction 
            for this QoS service."
    ::= { qosServicePolicyEntry 16 }

qosTxMin OBJECT-TYPE
    SYNTAX      Integer32
    MAX-ACCESS  read-only
    STATUS      current
    DESCRIPTION
            "The minimum transmit rate in Kbps for this QoS service."
    ::= { qosServicePolicyEntry 17 }

qosTxMax OBJECT-TYPE
    SYNTAX      Integer32
    MAX-ACCESS  read-only
    STATUS      current
    DESCRIPTION
            "The maximum transmit rate in Kbps for this QoS service."
    ::= { qosServicePolicyEntry 18 }

qosTxPackets OBJECT-TYPE
    SYNTAX      Counter32
    MAX-ACCESS  read-only
    STATUS      current
    DESCRIPTION
            "The number of packets transmitd for this QoS service."
    ::= { qosServicePolicyEntry 19 }

qosTxBytes OBJECT-TYPE
    SYNTAX      Counter32
    MAX-ACCESS  read-only
    STATUS      current
    DESCRIPTION
            "The number of bytes transmitd for this QoS service."
    ::= { qosServicePolicyEntry 20 }

qosTxDropped OBJECT-TYPE
    SYNTAX      Counter32
    MAX-ACCESS  read-only
    STATUS      current
    DESCRIPTION
            "The number of packets dropped in the transmit direction for this
            QoS service."
    ::= { qosServicePolicyEntry 21 }

qosTxOverlimits OBJECT-TYPE
    SYNTAX      Counter32
    MAX-ACCESS  read-only
    STATUS      current
    DESCRIPTION
            "The number of packets rate-shaped but not dropped in the transmit
            direction for this QoS service."
    ::= { qosServicePolicyEntry 22 }

qosTxBacklogPackets OBJECT-TYPE
    SYNTAX      Integer32
    MAX-ACCESS  read-only
    STATUS      current
    DESCRIPTION
            "The number of packets currently queued in the transmit direction 
            for this QoS service."
    ::= { qosServicePolicyEntry 23 }

qosTxBacklogBytes OBJECT-TYPE
    SYNTAX      Integer32
    MAX-ACCESS  read-only
    STATUS      current
    DESCRIPTION
            "The number of bytes currently queued in the transmit direction 
            for this QoS service."
    ::= { qosServicePolicyEntry 24 }

qosTxBacklogMs OBJECT-TYPE
    SYNTAX      Integer32
    MAX-ACCESS  read-only
    STATUS      current
    DESCRIPTION
            "The amount of time in milliseconds required to transmit the
            queued data at the class' maximum rate in the transmit direction 
            for this QoS service."
    ::= { qosServicePolicyEntry 25 }

qosServicePolicyGroup    OBJECT-GROUP
    OBJECTS { qosServicePolicyIndex, qosIfName, qosIfIndex, qosPolicy, qosService,
	qosType,
        qosPriority, qosRxMin, qosRxMax, qosRxPackets, qosRxBytes, qosRxDropped,
        qosRxOverlimits, qosRxBacklogPackets, qosRxBacklogBytes, qosRxBacklogMs,
        qosTxMin, qosTxMax, qosTxPackets, qosTxBytes, qosTxDropped, qosTxOverlimits,
        qosTxBacklogPackets, qosTxBacklogBytes, qosTxBacklogMs }
    STATUS  current
    DESCRIPTION
            "A collection of objects providing information applicable to
            all QoS Service Policys."
    ::= { qosGroups 1 }

END
